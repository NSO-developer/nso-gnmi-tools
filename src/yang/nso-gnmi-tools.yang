module nso-gnmi-tools {

  namespace "http://cisco.com/nso-gnmi-tools";
  prefix nso-gnmi-tools;


  import ietf-inet-types {
    prefix inet;
  }

  description
    "gNMI adapter configuration";

  revision 2023-06-20 {
    description
      "Initial revision.";
  }

  container nso-gnmi-tools {
    description "This is gNMI adapter config";
     leaf port {
      type inet:port-number;
      default 50061;
      description
        "Port is a valid port number to be used by gNMI server.";
    }
    container tls {
      leaf enabled {
        type boolean;
        default false;
        must ".='false' or (../keyFile and ../certFile)";
        description
          "'enabled' is either 'true' or 'false'. If 'true', the
          gNMI server uses TLS as a transport service.";
      }
      leaf keyFile {
        type string;
        description
          "Specifies which file that contains the private key for
          the certificate.";
      }
      leaf certFile {
        type string;
        description
          "Specifies which file that contains the server
          certificate. The certificate is either a self-signed
          test certificate or a genuine and validated certificate
          bought from a CA (Certificate Authority).";
      }
    }
  }
}
